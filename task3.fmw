FME workspace task3.fmw

Parameters:
- DestDataset_POSTGIS_RASTER =
- DestDataset_POSTGIS_RASTER_3 =
- DestDataset_TIFF =
- SourceDataset_SHAPEFILE =
- SourceDataset_TIFF =

Readers:
- SHAPEFILE_1: SHAPEFILE from $(SourceDataset_SHAPEFILE)
- TIFF_1: TIFF from $(SourceDataset_TIFF)

Writers:
- TIFF_2: TIFF to $(DestDataset_TIFF)
- POSTGIS_RASTER_1: POSTGIS_RASTER to $(DestDataset_POSTGIS_RASTER)
- POSTGIS_RASTER_2: POSTGIS_RASTER to $(DestDataset_POSTGIS_RASTER_3)

TIFF (reader TIFF_1)
    -> SpatialFilter [Candidate]
scotland_and_wales_const_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> TestFilter
TestFilter
    DEFAULT_VALUE = <UNFILTERED>
    TEST_LIST:
      "BOOL_OP,OR,COMPOSITE_TEST,""""""1 OR 2 OR 3"""""",TEST_CLAUSE,TEST @Value(FILE_NAME) = SOUTH_WALES_EAST_PER
      TEST @Value(FILE_NAME) = SOUTH_WALES_CENTRAL_PER
      TEST @Value(FILE_NAME) = SOUTH_WALES_WEST_PER",@Value(FILE_NAME) = SOUTH_WALES_EAST_PER
    @Value(FILE_NAME) = SOUTH_WALES_EAST_PER -> SpatialFilter [Filter]
    @Value(FILE_NAME) = SOUTH_WALES_EAST_PER -> Dissolver
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CLIPPEE]
Dissolver
    ACCUM_INPUT_ATTRS = Use Attributes From One Feature
    CLEANING_TOLERANCE = Automatic
    CONNECT_Z_MODE = First Wins
    DEAGGREGATE_INPUT = Yes
    AREA -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> RasterPaletteResolver
RasterPaletteResolver
    -> Exports (writer POSTGIS_RASTER_2)
Exports (writer POSTGIS_RASTER_2)
    attributes: name varchar(100), area_code varchar(3), descriptio varchar(50), file_name varchar(100), number int8, number0 int8, polygon_id int8, unit_id int8, code varchar(9), hectares float4, area float4, type_code varchar(2), descript0 varchar(25), type_cod0 varchar(3), descript1 varchar(36), _predicate text, _clipped char(3)
